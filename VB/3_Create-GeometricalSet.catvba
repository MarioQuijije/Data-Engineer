Attribute VB_Name = "CreateGeometricalSet"
Sub CATMain()
 
Dim partDocument1 As Document
Dim part1 As Part
 
'error handling
On Error Resume Next
 
Set partDocument1 = CATIA.ActiveDocument
Set part1 = partDocument1.Part
 
If Err.Number = 0 Then
 
Dim hybridBodies1 As HybridBodies
Set hybridBodies1 = part1.HybridBodies
 
Dim hybridBody2 As HybridBody
Set hybridBody2 = hybridBodies1.Add()
 
hybridBody2.Name = "NEW GEOMETRICAL SET"
 
'sets the newly created geometrical set as the in work object
part1.InWorkObject = hybridBody2
 part1.Update
 
'error handling
        Else
                MsgBox "Not a part document! Open in new window."
        End If
 
End Sub
