Attribute VB_Name = "ProductWith2Parts"
Sub CATMain()

Dim documents1 As Documents
Set documents1 = CATIA.Documents

Dim productDoc As ProductDocument
Set productDoc = documents1.Add("Product")

Dim rootProduct As Product
Set rootProduct = productDoc.Product

Dim childProduct As Product
Set childProduct = rootProduct.Products.AddNewComponent("Product", "")

Dim part1 As Product
Set part1 = childProduct.Products.AddNewComponent("Part", "")

Dim part2 As Product
Set part2 = childProduct.Products.AddNewComponent("Part", "")

End Sub
