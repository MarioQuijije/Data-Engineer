Attribute VB_Name = "CreatePoint"
Sub CATMain()

MsgBox ("Hello")

End Sub

Attribute VB_Name = "CreatePointCoordinates"
Sub Create_Point()

'----------------------------------------------------------
'--- Declaration CATIA objects ----------------------------
'----------------------------------------------------------
Dim PartDocument1 As PartDocument
Dim PartWorking As Part
Dim MyFactory As HybridShapeFactory
Dim MyHybridBody As HybridBody
Dim MyPoint As Point



'-----------------------------------------------------------
'--- Settings CATIA objects & variable VBA -----------------
'-----------------------------------------------------------
Set PartDocument1 = CATIA.ActiveDocument
Set PartWorking = PartDocument1.Part
Set MyFactory = PartWorking.HybridShapeFactory
Set MyHybridBody = PartWorking.HybridBodies.Item(1)


'-----------------------------------------------------------
'--- Creation of the point ---------------------------------
'-----------------------------------------------------------
Set MyPoint = MyFactory.AddNewPointCoord(10, 20, 30)
MyHybridBody.AppendHybridShape MyPoint
PartWorking.InWorkObject = MyPoint
PartWorking.UpdateObject MyPoint


End Sub

Attribute VB_Name = "MacroRecord"
Sub CATMain()

Dim PartDocument1 As PartDocument
Set PartDocument1 = CATIA.ActiveDocument

Dim boolean1 As Boolean
boolean1 = PartDocument1.Saved

Dim boolean2 As Boolean
boolean2 = PartDocument1.Saved

Dim boolean3 As Boolean
boolean3 = PartDocument1.Saved

Dim part1 As Part
Set part1 = PartDocument1.Part

Dim hybridBodies1 As HybridBodies
Set hybridBodies1 = part1.HybridBodies

Dim hybridBody1 As HybridBody
Set hybridBody1 = hybridBodies1.Add()

Dim hybridShapeFactory1 As HybridShapeFactory
Set hybridShapeFactory1 = part1.HybridShapeFactory

Dim hybridShapePointCoord1 As HybridShapePointCoord
Set hybridShapePointCoord1 = hybridShapeFactory1.AddNewPointCoord(0#, 0#, 0#)

Dim axisSystems1 As AxisSystems
Set axisSystems1 = part1.AxisSystems

Dim axisSystem1 As AxisSystem
Set axisSystem1 = axisSystems1.Item("Absolute Axis System")

Dim reference1 As Reference
Set reference1 = part1.CreateReferenceFromObject(axisSystem1)

hybridShapePointCoord1.RefAxisSystem = reference1

hybridBody1.AppendHybridShape hybridShapePointCoord1

part1.InWorkObject = hybridShapePointCoord1

part1.Update

Dim boolean4 As Boolean
boolean4 = PartDocument1.Saved

Set PartDocument1 = CATIA.ActiveDocument

Dim bSTR1 As String
bSTR1 = PartDocument1.FullName

End Sub

Attribute VB_Name = "UpdatedPoint"
Sub CATMain()

Dim PartDocument1 As PartDocument
Set PartDocument1 = CATIA.ActiveDocument

Dim boolean1 As Boolean
boolean1 = PartDocument1.Saved

Dim boolean2 As Boolean
boolean2 = PartDocument1.Saved

Dim boolean3 As Boolean
boolean3 = PartDocument1.Saved

Dim part1 As Part
Set part1 = PartDocument1.Part

Dim hybridBodies1 As HybridBodies
Set hybridBodies1 = part1.HybridBodies

Dim hybridBody1 As HybridBody
Set hybridBody1 = hybridBodies1.Add()

Dim hybridShapeFactory1 As HybridShapeFactory
Set hybridShapeFactory1 = part1.HybridShapeFactory

Dim hybridShapePointCoord1 As HybridShapePointCoord
Set hybridShapePointCoord1 = hybridShapeFactory1.AddNewPointCoord(100#, 100#, 100#)

Dim axisSystems1 As AxisSystems
Set axisSystems1 = part1.AxisSystems

Dim axisSystem1 As AxisSystem
Set axisSystem1 = axisSystems1.Item("Absolute Axis System")

Dim reference1 As Reference
Set reference1 = part1.CreateReferenceFromObject(axisSystem1)

hybridShapePointCoord1.RefAxisSystem = reference1

hybridBody1.AppendHybridShape hybridShapePointCoord1

part1.InWorkObject = hybridShapePointCoord1

part1.Update

Dim boolean4 As Boolean
boolean4 = PartDocument1.Saved

Set PartDocument1 = CATIA.ActiveDocument

Dim bSTR1 As String
bSTR1 = PartDocument1.FullName

End Sub
