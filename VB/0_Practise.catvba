Attribute VB_Name = "Module1"
Sub CatMain()

Dim mydoc As Document
Set mydoc = CATIA.Documents.Add("Part")

Dim Part1 As Part
Set Part1 = mydoc.Part

Dim Bodies1 As Bodies
Set Bodies1 = Part1.Bodies


End Sub

Attribute VB_Name = "Practise"
Sub CatMain()

Dim mydoc As Document
Set mydoc = CATIA.Documents.Add("Part")

End Sub
