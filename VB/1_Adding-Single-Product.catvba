Attribute VB_Name = "AddingSingleProduct"
Sub CATMain()

Dim doc1 As Document
Set doc1 = CATIA.Documents.Add("Product")

Dim P1 As Products
Set P1 = CATIA.ActiveDocument.Product

Dim P2 As Product
Set P2 = P1.AddNewComponent("Part", "03")

End Sub
