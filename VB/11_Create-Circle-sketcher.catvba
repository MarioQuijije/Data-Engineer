Attribute VB_Name = "CreateCircleinSketch"
Sub CatMain()

Dim mydoc As Document
Set mydoc = CATIA.Documents.Add("Part")

Dim Part1 As Part
Set Part1 = mydoc.Part

Dim Bodies As Bodies
Set Bodies = Part1.Bodies

Dim Body1 As Body
Set Body1 = Bodies.Item("PartBody")

Dim Sketches1 As Sketches
Set Sketches1 = Body1.Sketches

Dim OriginElements As OriginElements
Set OriginElements = Part1.OriginElements

Dim Reference1 As Reference
Set Reference1 = OriginElements.PlaneXY

Dim Sketch1 As Sketch
Set Sketch1 = Sketches1.Add(Reference1)

'Create Tool - box

Dim work As Factory2D
Set work = Sketch1.OpenEdition

Dim Circle1 As Circle2D
Set Circle1 = work.CreateClosedCircle(0, 0, 50)

Sketch1.CloseEdition
Part1.Update

End Sub
