Attribute VB_Name = "AddingNewProductRoot"
Sub CATMain()

'1) Prolog'

'Create a new product document by adding a document with the Product type
'to the document collection of the CATIA application.
Dim oProductDoc As Document
Set oProductDoc = CATIA.Documents.Add("Product")

'Retrieve the root product.
Dim oRootProduct As Product
Set oRootProduct = oProductDoc.Product

'Declare the root product's part number and name.
oRootProduct.PartNumber = "Root"
oRootProduct.Name = "The_Root_Product"

'Retrieve the product's collection under the root product.
Dim oRootChildren As Products
Set oRootChildren = oRootProduct.Products

'2) Adding a New Product'

'Add a new product to the collection. This adds both a product reference
'and a product component.
Dim oChildProduct1 As Product
Set oChildProduct1 = oRootChildren.AddNewProduct("Child_1_Type")

'Declare the part number and name for this product.
oChildProduct1.PartNumber = "Child_001"
oChildProduct1.Name = "1st_Child"

'3) Assigning a Master Shape Representation to the New Product'

'Add a representation to this product using an existing part and reframe
'the viewer to display the part completely.
oChildProduct1.AddMasterShapeRepresentation sDocPath & "CAAPstPad1_1.CATPart"
CATIA.ActiveWindow.ActiveViewer.Reframe

'4) Adding a Second New Product'

'Add another product to the root product's collection.  This adds both
'a product reference and a product component.
Dim oChildProduct2 As Product
Set oChildProduct2 = oRootChildren.AddNewProduct("Child_2_Type")


'Declare the part number and name for this product.
oChildProduct2.PartNumber = "Child_002"
oChildProduct2.Name = "2nd_Child"

'5) Assigning a Master Shape Representation to the Second New Product'

'Add a representation to this product using an existing part and reframe
'the viewer to display the part completely.
oChildProduct2.AddMasterShapeRepresentation sDocPath & "CAAPstPad1_2.CATPart"
CATIA.ActiveWindow.ActiveViewer.Reframe

End Sub
