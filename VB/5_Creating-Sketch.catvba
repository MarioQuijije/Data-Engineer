Attribute VB_Name = "CreatingSketch"
Sub CATMain()

Dim mydoc As Document
Set mydoc = CATIA.Documents.Add("Part")

Dim Part1 As Part
Set Part1 = mydoc.Part

Dim Bodies1 As Bodies
Set Bodies1 = Part1.Bodies

Dim Body1 As Body
Set Body1 = Bodies1.Item("PartBody")

Dim Sketches1 As Sketches
Set Sketches = Body1.Sketches


End Sub
